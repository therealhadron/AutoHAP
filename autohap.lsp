(defun c:autohap () 
  (setq user_selection (ssget))
  (setq count (sslength user_selection))
  (setq i 0)
  (setq output_file (getfiled "Select output file " "autocad_output" "txt" 1))
  (setq file (open output_file "w"))
  (setq warning 0)
  
  ; Check if units are in decimal form. If not change to decimal form
  (setq current_lunits (getvar "lunits"))
  (if (/= current_lunits 2)
    (setvar "lunits" 2)
  )
  
  (if user_selection
    (repeat count
      (setq entity (ssname user_selection i))
      (setq entity_data (entget entity))
      (if (= (cdr (assoc 0 entity_data)) "LWPOLYLINE")
        (progn
          (write-line (strcat "{") file)
          (setq is_closed (cdr (assoc 70 entity_data)))
          (if (= is_closed 1)
            (progn
              (setq layer_name (cdr (assoc 8 entity_data)))
              (setq vertices (mapcar 'cdr (vl-remove-if '(lambda (x) (/= 10 (car x))) entity_data)))
              (setq filter_list (vl-remove nil vertices))

              (write-line (strcat "<Layer_name>" layer_name) file)

              (write-line (strcat "<Coordinates>") file)
              (foreach vertex filter_list
                (write-line (strcat "(" (rtos (car vertex)) "," (rtos (cadr vertex)) ")") file)
              )
              (write-line (strcat "}") file)
            )
            (setq warning 1)
          )
        )
      )
      (if (= (cdr (assoc 0 entity_data)) "LINE")
        (progn
          (setq layer_name (cdr (assoc 8 entity_data)))
          (setq start_point (cdr (assoc 10 entity_data)))
          (setq end_point (cdr (assoc 11 entity_data)))
          (write-line (strcat "{") file)
          (write-line (strcat "<Layer_name>" layer_name) file)
          (write-line (strcat "<start_point>(" (rtos (car start_point)) "," (rtos (cadr start_point)) ")") file)
          (write-line (strcat "<end_point>(" (rtos (car end_point)) "," (rtos (cadr end_point)) ")") file)
          (write-line (strcat "}") file)
        )
      )
      (if (= (cdr (assoc 0 entity_data)) "MTEXT")
        (progn
          (write-line (strcat "{") file)
          (setq mtext_contents (cdr (assoc 1 entity_data)))
          (setq mtext_layer_name (cdr (assoc 8 entity_data)))
          (setq mtext_location (cdr (assoc 10 entity_data)))
          (write-line (strcat "<Layer_name>" mtext_layer_name) file)
          (write-line (strcat "<Text_contents>" mtext_contents) file)
          (write-line (strcat "<Coordinates>") file)
          (write-line (strcat "(" (rtos (car mtext_location)) "," (rtos (cadr mtext_location)) ")") file)
          (write-line (strcat "},") file)
        )
      )
      (setq i (1+ i))
    )
    (princ "")
  )
  (close file)
  (setvar "lunits" current_lunits)
  (if (= warning 1)
    (princ "Warning selection includes non-closed polylines. Double check all polylines to ensure they are closed")
    (progn
      (princ "Successfully Saved")
      ; Begin execution of python and autoit scripts
      (setq dwgPath (getvar "DWGPREFIX"))
      (setq startFilePath (strcat dwgPath "/start.bat"))
      (startapp startFilePath)
    )
  )
)
